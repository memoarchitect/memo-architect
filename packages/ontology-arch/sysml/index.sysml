// ─── MEMO Ontology Arch — Package Index ──────────────────────────────────────
//
// Single-entry-point aggregate for SysAnd interchange projects.
// Import this file to bring all MEMO architecture layers into scope.
// ─────────────────────────────────────────────────────────────────────────────

package MEMO_Ontology_Arch {
    import MEMO_Ontology_Arch_Operational::*;
    import MEMO_Ontology_Arch_Functional::*;
    import MEMO_Ontology_Arch_Logical::*;
    import MEMO_Ontology_Arch_Software::*;
    import MEMO_Ontology_Arch_SoftwareExtension_ROS::*;
    import MEMO_Ontology_Arch_Hardware::*;
    import MEMO_Ontology_Arch_Behavioral::*;
    import MEMO_Ontology_Arch_Verification::*;
    import MEMO_Ontology_Arch_Safety::*;
    import MEMO_Ontology_Arch_Security::*;
    import MEMO_Ontology_Arch_Privacy::*;
    import MEMO_Ontology_Arch_Relationships::*;
    import MEMO_Ontology_Arch_Axioms::*;
}
