// ============================================================================
// MEMO Framework Ontology — SysML v2 Package (Comprehensive)
// Version: 2.0.0
//
// 60+ entity types across 9 architectural domains.
// FRAMEWORK-level only — domain configs specialize these types.
//
// This index re-exports all domain packages as a single MEMO_Ontology.
// ============================================================================

package MEMO_Ontology {
    import MEMO_Ontology_Business::*;
    import MEMO_Ontology_Operational::*;
    import MEMO_Ontology_Requirements::*;
    import MEMO_Ontology_Risk::*;
    import MEMO_Ontology_Functional::*;
    import MEMO_Ontology_Logical::*;
    import MEMO_Ontology_Physical::*;
    import MEMO_Ontology_Software::*;
    import MEMO_Ontology_Interfaces::*;
    import MEMO_Ontology_Analysis::*;
    import MEMO_Ontology_UI::*;
    import MEMO_Ontology_CrossCutting::*;
    import MEMO_Ontology_Relationships::*;
}
