package MEMO_Ontology_Medical_Relationships {

    connection def PlansClinicalEvaluation {
        end plan : ClinicalEvaluationPlan [1];
        end subject[1];
    }

    connection def EvaluatesClinicalClaim {
        end report : ClinicalEvaluationReport [1];
        end claim : ClinicalClaim [1];
    }

    connection def SupportsClinicalClaim {
        end evidence : ClinicalEvidenceArtifact [1];
        end claim : ClinicalClaim [1];
    }

    connection def ClaimsClinicalBenefit {
        end claim : ClinicalClaim [1];
        end benefit : ClinicalBenefit [1];
    }

    connection def ClaimsForUse {
        end claim : ClinicalClaim [1];
        end subject[1];
    }

    connection def ManufacturesSubject {
        end procedure : ManufacturingProcedure [1];
        end subject[1];
    }

    connection def InstallsSubject {
        end procedure : InstallationProcedure [1];
        end subject[1];
    }

    connection def ServicesSubject {
        end procedure : ServiceProcedure [1];
        end subject[1];
    }

    connection def MaintainsSubject {
        end procedure : PreventiveMaintenanceProcedure [1];
        end subject[1];
    }

    connection def CalibratesSubject {
        end procedure : CalibrationProcedure [1];
        end subject[1];
    }

    connection def QualifiesInstallation {
        end qualification : InstallationQualification [1];
        end subject[1];
    }

    connection def Mitigates {
        end control : RiskControl [1];
        end hazard : Hazard [1];
    }

    connection def Causes {
        end hazard : Hazard [1];
        end situation : HazardousSituation [1];
    }

    connection def LeadsTo {
        end situation : HazardousSituation [1];
        end harm : Harm [1];
    }

    connection def Identifies {
        end risk : Risk [1];
        end hazard : Hazard [1];
    }

    connection def PlansRiskManagement {
        end plan : RiskManagementPlan [1];
        end subject[1];
    }

    connection def AssessesResidualRisk {
        end evaluation : ResidualRiskEvaluation [1];
        end subject[1];
    }

    connection def WeighsAgainstBenefit {
        end assessment : BenefitRiskAssessment [1];
        end benefit : ClinicalBenefit [1];
    }

    connection def ConcludesBenefitRisk {
        end assessment : BenefitRiskAssessment [1];
        end subject[1];
    }

    connection def ConcludesOverallResidualRisk {
        end report : RiskManagementReport [1];
        end evaluation : OverallResidualRiskEvaluation [1];
    }

    connection def MonitorsRiskSubject {
        end signal : ProductionPostProductionSignal [1];
        end subject[1];
    }

    connection def ModelsThreat {
        end model : ThreatModel [1];
        end threat : ThreatScenario [1];
    }

    connection def ThreatensAsset {
        end threat : ThreatScenario [1];
        end asset : CyberAsset [1];
    }

    connection def ExploitsVulnerability {
        end threat : ThreatScenario [1];
        end vulnerability : Vulnerability [1];
    }

    connection def MitigatesThreat {
        end control : SecurityControl [1];
        end threat : ThreatScenario [1];
    }

    connection def SecuresInterface {
        end control : SecurityControl [1];
        end dataInterface : DataInterface [1];
    }

    connection def MaintainsSbom {
        end sbom : SBOMArtifact [1];
        end subject[1];
    }

    connection def SupportsSecureUpdate {
        end capability : SecureUpdateCapability [1];
        end subject[1];
    }

    connection def ClassifiesData {
        end classification : PersonalDataCategory [1];
        end subject[1];
    }

    connection def ProcessesData {
        end activity : DataProcessingActivity [1];
        end subject[1];
    }

    connection def ProvidesPrivacyNotice {
        end subject[1];
        end notice : PrivacyNotice [1];
    }

    connection def AssessesPrivacyImpact {
        end assessment : PrivacyImpactAssessment [1];
        end subject[1];
    }

    connection def RespondsToDataSubjectRequest {
        end request : DataSubjectRequest [1];
        end subject[1];
    }

    connection def AnalyzesFailureMode {
        end analysis : FailureModesAndEffectsAnalysis [1];
        end failureMode : FailureMode [1];
    }

    connection def HasFailureCause {
        end failureMode : FailureMode [1];
        end cause : FailureCause [1];
    }

    connection def ResultsInFailureEffect {
        end failureMode : FailureMode [1];
        end effect : FailureEffect [1];
    }

    connection def EscalatesToRisk {
        end effect : FailureEffect [1];
        end subject[1];
    }

    connection def DetectsFailureMode {
        end control : RiskControl [1];
        end failureMode : FailureMode [1];
    }

    connection def DefinesTopEvent {
        end analysis : FaultTreeAnalysis [1];
        end topEvent : TopEvent [1];
    }

    connection def UsesGate {
        end event[1];
        end gate : FaultTreeGate [1];
    }

    connection def ContributesToEvent {
        end contributor[1];
        end event[1];
    }

    connection def TriggersHazardousSituation {
        end event[1];
        end situation : HazardousSituation [1];
    }

    connection def Preserves {
        end function : SafetyFunction [1];
        end performance : EssentialPerformance [1];
    }

    connection def AddressesUseError {
        end uiRequirement : UserInterfaceRequirement [1];
        end useError : UseError [1];
    }

    connection def AnalyzesUseError {
        end analysis : UseErrorAnalysis [1];
        end useError : UseError [1];
    }

    connection def ExposesUseError {
        end scenario : OperationalScenario [1];
        end useError : UseError [1];
    }

    connection def SpecifiesScenario {
        end specification : UseSpecification [1];
        end scenario : OperationalScenario [1];
    }

    connection def EvaluatesRequirement {
        end evaluation : ValidationCase [1];
        end uiRequirement : UserInterfaceRequirement [1];
    }

    connection def ContributesToHazard {
        end useError : UseError [1];
        end hazard : Hazard [1];
    }

    connection def SupportsOperatingFunction {
        end performance : EssentialPerformance [1];
        end function : PrimaryOperatingFunction [1];
    }

    connection def DefinesLossCondition {
        end performance : EssentialPerformance [1];
        end condition : EssentialPerformanceLossCondition [1];
    }

    connection def ProtectsEssentialPerformance {
        end control : RiskControl [1];
        end performance : EssentialPerformance [1];
    }

    connection def AppliesStandardRequirement {
        end standardRequirement : RegulatoryRequirement [1];
        end subject[1];
    }

    connection def ImplementsRiskControl {
        end implementer[1];
        end control : RiskControl [1];
    }

    connection def GovernsActivity {
        end process : SoftwareLifecycleProcess [1];
        end activity : SoftwareLifecycleActivity [1];
    }

    connection def ProducesWorkProduct {
        end activity : SoftwareLifecycleActivity [1];
        end workProduct : SoftwareWorkProduct [1];
    }

    connection def Evidences {
        end evidence : ComplianceEvidence [1];
        end subject[1];
    }

    connection def Documents {
        end record : QMSRecord [1];
        end subject[1];
    }
}
