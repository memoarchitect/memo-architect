package MEMO_Ontology_MedicalArch_Relationships {

    connection def Aggregation {
        end whole[1];
        end part[0..*];
    }

    connection def Association {
        end source[1];
        end target[1];
    }

    connection def TraceTo {
        end source[1];
        end target[1];
    }

    connection def Refines {
        end refined[1];
        end refiner[1];
    }

    connection def Derives {
        end source[1];
        end derived[1];
    }

    connection def Constrains {
        end constraint[1];
        end constrained[1];
    }

    connection def AllocateTo {
        end function[1];
        end structure[1];
    }

    connection def ComposedOf {
        end whole[1];
        end part[0..*];
    }

    connection def DecomposedBy {
        end parent[1];
        end child[0..*];
    }

    connection def Dependency {
        end client[1];
        end supplier[1];
    }

    connection def ExposesInterface {
        end provider[1];
        end dataInterface : DataInterface [1];
    }

    connection def Realization {
        end realizing[1];
        end realized[1];
    }

    connection def Satisfy {
        end satisfiedBy[1];
        end satisfies : Requirement [1];
    }

    connection def Verify {
        end verifiedBy[1];
        end verifies[1];
    }

    connection def Flow {
        end source[1];
        end target[1];
    }

    connection def Succession {
        end predecessor[1];
        end successor[1];
    }

    // ─── Operational (folded from ontology-extensions/operational-advanced) ──
    connection def HasSubProcedure {
        end procedure : Procedure [1];
        end subProcedure : Procedure [0..*];
    }

    connection def PerformedBy {
        end procedure : Procedure [1];
        end performer : OperationalActor [1];
    }

    connection def PerformedOn {
        end procedure : Procedure [1];
        end subject : OperationalEntity [1];
    }

    connection def OccursIn {
        end procedure : Procedure [1];
        end environment : OperationalEnvironment [1];
    }

    connection def UsesResource {
        end procedure : Procedure [1];
        end resource[1];
    }

    connection def HasEquipment {
        end environment : OperationalEnvironment [1];
        end equipment[0..*];
    }

    connection def HasPersonnel {
        end environment : OperationalEnvironment [1];
        end personnel : OperationalActor [0..*];
    }

    connection def ContainsSubstance {
        end environment : OperationalEnvironment [1];
        end substance : Substance [0..*];
    }

    // ─── Platform / messaging (folded from ontology-extensions/platform-core) ──
    connection def HasEndpoint {
        end dataInterface : DataInterface [1];
        end endpoint : Port [1];
    }

    connection def ImplementsProtocol {
        end subject[1];
        end protocol : CommunicationProtocol [1];
    }

    connection def ConformsToProfile {
        end subject[1];
        end profile : InteroperabilityProfile [1];
    }

    connection def CarriesExchangeItem {
        end dataInterface : DataInterface [1];
        end exchangeItem : ExchangeItem [1];
    }

    connection def PublishesTo {
        end publisher[1];
        end channel : PublishSubscribeChannel [1];
    }

    connection def SubscribesTo {
        end subscriber[1];
        end channel : PublishSubscribeChannel [1];
    }

    connection def PublishesMessage {
        end publisher[1];
        end message : Message [1];
    }

    connection def ConsumesMessage {
        end subscriber[1];
        end message : Message [1];
    }

    connection def ServesInterface {
        end provider[1];
        end service : RequestResponseInterface [1];
    }

    connection def InvokesInterface {
        end consumer[1];
        end service : RequestResponseInterface [1];
    }

    connection def CarriesRequestMessage {
        end service : RequestResponseInterface [1];
        end request : RequestMessage [1];
    }

    connection def CarriesResponseMessage {
        end service : RequestResponseInterface [1];
        end response : ResponseMessage [1];
    }

    connection def BrokersChannel {
        end broker : MessageBroker [1];
        end channel : PublishSubscribeChannel [1];
    }

    connection def RoutesToChannel {
        end sourceChannel : PublishSubscribeChannel [1];
        end targetChannel : PublishSubscribeChannel [1];
    }

    connection def DefinesMessageSchema {
        end schema : MessageSchema [1];
        end message : Message [1];
    }

    connection def HasMessageField {
        end schema : MessageSchema [1];
        end field : MessageField [0..*];
    }

    connection def ParticipatesInSystemOfSystems {
        end system[1];
        end systemOfSystems : SystemOfSystems [1];
    }
}
