package MEMO_Ontology_MedicalArch {
    // MBSE backbone (Arcadia / ISO 42010 layers)
    import MEMO_Ontology_MedicalArch_Operational::*;
    import MEMO_Ontology_MedicalArch_Operational_Purpose::*;
    import MEMO_Ontology_MedicalArch_System::*;
    import MEMO_Ontology_MedicalArch_Requirements::*;
    import MEMO_Ontology_MedicalArch_Functional::*;
    import MEMO_Ontology_MedicalArch_Logical::*;
    import MEMO_Ontology_MedicalArch_Hardware::*;
    import MEMO_Ontology_MedicalArch_Software::*;
    import MEMO_Ontology_MedicalArch_Interfaces::*;
    import MEMO_Ontology_MedicalArch_Analysis::*;
    import MEMO_Ontology_MedicalArch_Verification::*;
    import MEMO_Ontology_MedicalArch_Relationships::*;

    // Medical-device architecture kinds (UI + operational user activity)
    import MEMO_Ontology_MedicalArch_UI::*;
    import MEMO_Ontology_MedicalArch_Development::*;
}
