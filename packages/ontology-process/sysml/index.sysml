// ─── MEMO Ontology Process — Package Index ───────────────────────────────────
//
// Single-entry-point aggregate for SysAnd interchange projects.
// Import this file to bring all MEMO process standards into scope.
// ─────────────────────────────────────────────────────────────────────────────

package MEMO_Ontology_Process {
    import MEMO_Ontology_Process_Common::*;
    import MEMO_Ontology_Process_ISO14971::*;
    import MEMO_Ontology_Process_IEC62304::*;
    import MEMO_Ontology_Process_ISO13485::*;
    import MEMO_Ontology_Process_IEC60601::*;
    import MEMO_Ontology_Process_ISO14155::*;
    import MEMO_Ontology_Process_ISO27001_27701::*;
    import MEMO_Ontology_Process_FDA21CFR820::*;
    import MEMO_Ontology_Process_EUMDR::*;
    import MEMO_Ontology_Process_Relationships::*;
}
