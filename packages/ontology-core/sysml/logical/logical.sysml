package MEMO_Ontology_Core_Logical {

    part def LogicalComponent {
        attribute name : String;
        attribute level : String;
    }

    part def ArchitectureDecision {
        attribute name : String;
    }

    part def QualityAttribute {
        attribute name : String;
    }
}
