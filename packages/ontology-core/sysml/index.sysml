package MEMO_Ontology_Core {
    import MEMO_Ontology_Core_Operational::*;
    import MEMO_Ontology_Core_Operational_Purpose::*;
    import MEMO_Ontology_Core_System::*;
    import MEMO_Ontology_Core_Requirements::*;
    import MEMO_Ontology_Core_Functional::*;
    import MEMO_Ontology_Core_Logical::*;
    import MEMO_Ontology_Core_Hardware::*;
    import MEMO_Ontology_Core_Software::*;
    import MEMO_Ontology_Core_Interfaces::*;
    import MEMO_Ontology_Core_Analysis::*;
    import MEMO_Ontology_Core_Verification::*;
    import MEMO_Ontology_Core_Relationships::*;
}
