package MEMO_Ontology_MedicalProcess_Clinical_Trial {
    import MEMO_Ontology_MedicalArch::*;
    import MEMO_Ontology_MedicalProcess::*;
    import MEMO_Ontology_MedicalProcess_ClinicalContext::*;
    import MEMO_Ontology_MedicalProcess_ClinicalEvaluation::*;
    import MEMO_Ontology_MedicalProcess_Clinical_Relationships::*;
}
