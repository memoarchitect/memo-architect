package MEMO_ARCH_Risk {
    doc /* Configuration Item (CI) aggregator for MEMO architecture risk domain.
         * Re-exports all risk-related packages for Sysand build. */
    public import memo::architecture::risk::*;
}
