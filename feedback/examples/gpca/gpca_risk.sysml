package md::examples::gpca::risk {
    private import md::architecture::risk::*;
    part overdoseHazard : Hazard { attribute id = "HZ-001"; attribute name = "Overdose"; attribute hazardType = HazardTypeKind::overdose; attribute foreseeable = true; }
    part seqFrequentBolus : SequenceOfEvents { attribute id = "SEQ-001"; attribute name = "FrequentPatientBolusSequence"; attribute initiatingEvent = "Patient bolus request during lockout"; attribute contributingFactors = "Lockout violation or max bolus exceeded"; }
    part hsExcessInfusion : HazardousSituation { attribute id = "HS-001"; attribute name = "PatientExposedToExcessInfusion"; attribute exposedPersons = "patient"; attribute operatingCondition = "ACTIVE therapy"; }
    part harmRespiratoryDepression : Harm { attribute id = "HM-001"; attribute name = "RespiratoryDepression"; attribute clinicalImpact = "serious injury or death"; attribute reversibility = "potentially irreversible"; attribute criticality = CriticalityKind::catastrophic; }
    part riskBefore : RiskBeforeMitigation { attribute id = "RISK-B-001"; attribute name = "OverdoseRiskBeforeMitigation"; attribute driverKind = "risk"; attribute probabilityEstimate = "Occasional"; attribute severityEstimate = "Catastrophic"; attribute riskLevel = "High"; attribute acceptability = "Unacceptable"; attribute estimationBasis = "mode and bolus hazard analysis"; attribute analysisContext = "patient bolus and active mode control"; attribute foreseeableMisuseIncluded = true; }
    part riskMatrix : RiskMatrix { attribute id = "RMX-001"; attribute name = "StandardRiskMatrix"; attribute probabilityScaleDefinition = "Remote, Occasional, Probable"; attribute severityScaleDefinition = "Minor, Serious, Catastrophic"; attribute riskLevelMapping = "matrix based"; attribute acceptabilityThresholds = "High unacceptable"; }
    part lockoutControl : RiskControl { attribute id = "RC-001"; attribute name = "LockoutAndMaxBolusEnforcement"; attribute controlKind = RiskControlKind::inherentSafeDesign; attribute implementationKind = "ignore and alarm on invalid bolus conditions"; attribute verificationStatus = "planned"; }
    part riskAfter : RiskAfterMitigation { attribute id = "RISK-A-001"; attribute name = "OverdoseRiskAfterMitigation"; attribute driverKind = "risk"; attribute probabilityEstimate = "Remote"; attribute severityEstimate = "Catastrophic"; attribute riskLevel = "Medium"; attribute acceptability = "Conditionally Acceptable"; attribute residualProbability = "Remote"; attribute residualSeverity = "Catastrophic"; attribute residualAcceptability = "Acceptable with review"; attribute benefitRiskRequired = false; }
    part residualEval : OverallResidualRiskEvaluation { attribute id = "RREV-001"; attribute name = "OverallResidualRiskEvaluation"; attribute conclusion = "Residual overdose risk acceptable with lockout, pause-on-alarm, and verification."; attribute reviewer = "Safety review"; }
}
