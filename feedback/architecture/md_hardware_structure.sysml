package md::architecture::hardware_structure {
    private import md::core::common::*;
    part def HardwareAssembly :> ArchitectureElement { attribute responsibility : String; attribute safetyRole : String; }
}
