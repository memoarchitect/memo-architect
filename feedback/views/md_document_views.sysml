package md::views::document_views {
    private import md::views::core::*;
    private import md::core::enumerations::*;

    part def DocumentView :> DocumentBackedView {
        attribute viewKind : DocumentViewKind;
    }

    part def CybersecurityThreatModelView :> DocumentView {
        attribute viewKind = DocumentViewKind::ThreatModel;
        attribute generationRule = "Include assets, trust boundaries, threat scenarios, vulnerabilities, mitigations, and trace links to safety/privacy concerns.";
        attribute outputKind = {ViewOutputKind::documentSection};
        attribute presentationKind = {PresentationKind::narrativeSection};
    }

    part def CybersecurityAssessmentView :> DocumentView {
        attribute viewKind = DocumentViewKind::CybersecurityAssessment;
        attribute generationRule = "Include cyber risks, exploitability, mitigations, security requirements, verification, residual risk, and postmarket evidence references.";
        attribute outputKind = {ViewOutputKind::documentSection};
        attribute presentationKind = {PresentationKind::riskTable};
    }
}
