// ── Ontology Selection ───────────────────────────────────────────────────────
//
// Auto-generated by MEMO when the user saves their ontology selection in the
// Ontology Viewer. Do not edit manually — use the Ontology Viewer instead.
//
// This file is the SysML v2 source-of-truth for which ontology packages are
// active in this project. Each import declaration brings that ontology's
// namespace into scope for the project's model files.
// ─────────────────────────────────────────────────────────────────────────────

package OntologySelection {
    import MEMO_Ontology_Arch::*;
    import MEMO_Ontology_Process::*;
}
